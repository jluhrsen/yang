module ietf-netconf-light {

  namespace "urn:ietf:params:xml:ns:yang:ietf-netconf-light";
  prefix "ncl";

  organization
   "IETF NETCONF (Network Configuration Protocol) Working Group";

  contact
   "WG Web:   <http://tools.ietf.org/wg/netconf/>
    WG List:  <mailto:netconf@ietf.org>

    WG Chair: Bert Wijnen
              <mailto:bertietf@bwijnen.net>

    WG Chair: Mehmet Ersue
              <mailto:mehmet.ersue@nsn.com>

    Editor: Vladislav Perelman
            <mailto:v.perelman@jacobs-university.de>

    Editor: Juergen Schoenwaelder
            <mailto:j.schoenwaelder@jacobs-university.de>

    Editor: Mehmet Ersue
            <mailto:mehmet.ersue@nsn.com>

    Editor: Kent Watsen
            <mailto:kwatsen@juniper.net>";

  description

   "This module defines the base NETCONF protocol defined in RFC 6241
    as a suite of optionally implemented features.  The NETCONF Light
    capability is expected to be advertized in the server's <hello>
    message in lieu of the traditional base NETCONF capability.  By
    advertizing this capability, servers can indentify which parts of
    the NETCONF protocol are supported.  For the most part, NETCONF
    Light defines a one-to-one mapping between base protocol
    operations and features enabling them; exceptions include
    <get-config>, which has one feature to enable the RPC and another
    to enable subtree-filtering, and <lock>/<unlock>, which share a
    feature called \"locking\".  Advertizing all NETCONF Light
    features is equivalent to advertizing the NETCONF base capability
    itself.

    Copyright (c) 2012 IETF Trust and the persons identified as
    authors of the code. All rights reserved.

    Redistribution and use in source and binary forms, with or
    without modification, is permitted pursuant to, and subject
    to the license terms contained in, the Simplified BSD
    License set forth in Section 4.c of the IETF Trust's
    Legal Provisions Relating to IETF Documents
    (http://trustee.ietf.org/license-info).

    This version of this YANG module is part of RFC XXXX; see
    the RFC itself for full legal notices.";
  // RFC Ed.: replace XXXX with actual RFC number and
  // remove this note

  // RFC Ed.: remove this note
  // Note: extracted from draft-schoenw-netconf-light-01.txt

  // RFC Ed.: please update the date to the date of publication

  revision 2012-01-12 {
    description "Initial version.";
    reference "RFC XXXX: Network Configuration Protocol for
                         Constrained Devices (NETCONF Light)";
  }
}
