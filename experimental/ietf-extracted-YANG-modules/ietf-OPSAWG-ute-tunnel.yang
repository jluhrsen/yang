module ietf-OPSAWG-ute-tunnel {
    namespace "urn:ietf:params:xml:ns:yang:ietf-OPSAWG-ute-tunnel";
    prefix ute-tunnel;

    import ietf-yang-types {prefix yang;}
    import ietf-inet-types {prefix inet;}
    import ietf-ac-pub-type {prefix ac-type;}

    organization "IETF OPSA Working Group";
    contact
    "Editor:   Robin Li
                <mailto:lizhenbin@huawei.com>";
    description ;
    revision 2017-03-11{
        description "Initial version";
        reference ;
    }

    typedef manage-protocol{
        type enumeration{
            enum netconf{
                value 0;
            }
        }
    }

    typedef control-protocol{
        type enumeration{
            enum pcep{
                value 0;
            }
            enum netconf{
                value 1;
            }
        }
    }

    typedef manage-type{
        type enumeration{
            enum ne{
                value 0;
                description "Tunnel is create and delete,modified by ne";
            }
            enum controller{
                value 1;
                description "tunne is create,delete andmodified by controller";
            }
        }
    }

    typedef control-mode{
        type enumeration{
            enum delegate{
                value 0;
            }
            enum report{
                value 1;
            }
            enum none{
                value 2;
            }
        }
    }

    typedef tunnel-down-clear-reason {
        type enumeration {
              enum up {
                   value 1;
                   description "indicates the tunnel is down .";
              }
              enum delete {
                    value 2;
                    description "indicates the tunnel is delete .";
              }
        }
    }
    typedef oper-type {
        type enumeration {
              enum update {
                   value 0;
                   description "indicates the tunnel lsp is update .";
              }
              enum remove {
                    value 1;
                    description "indicates the tunnel lsp is remove .";
              }
        }
    }

   // Identities

    identity tunl-type {
    }
    identity te{
        base tunl-type;
    }
    identity uni{
        base tunl-type;
    }

   // Groupings

    grouping src-or-dst{
        leaf ne-id{
            type yanguuid;
        }
        leaf ip-address{
            type inetip-address;
            mandatory true;
        }
    }

   // Main container of cfg

    container ute-tunnel-cfg{
        container p2p-tunnel{
            container tunnels{
                list tunnel{
                    key tunnel-name;
                    leaf tunnel-name{
                        type string {
                            length 1..64;
                        }
                        description "Tunnel Name";
                    }
                    leaf user-label{
                        type string {
                            length 0..242;
                        }
                    }
                    leaf tunnel-type{
                        type identityref{
                            base tunl-type;
                        }
                        mandatory true;
                    }
                    leaf admin-status{
                        type ac-typeadmin-status;
                        default admin-up;
                    }
                    leaf sym-tunnel-name{
                        type string {
                            length 1..255;
                        }
                    }
                    leaf mtu{
                        type uint32 {
                            range 46..9600;
                        }
                        default 1500;
                    }
                    leaf manage-type{
                        type manage-type;
                    }
                    leaf manage-protocol{
                        type manage-protocol;
                    }
                    leaf control-protocol {
                            description "The tunnel path's control protocol type";
                        type control-protocol;
                        default pcep;
                    }
                    leaf control-mode{
                        type control-mode;
                    }
                    leaf adopt {
                        description "Tunnel is adopted by controller and can be relayed by services";
                        type boolean;
                        default false;
                    }
                    leaf ip-address{
                        type inetipv4-address;
                    }
                    leaf ip-unnumbered{
                        type string {
                            length 1..64;
                        }
                    }
                    container source{
                        uses src-or-dst;
                    }
                    container destination{
                        uses src-or-dst;
                    }
                }
            }

            container bidirection-co-route-groups{
                list co-route-group{
                    key co-route-name;
                    leaf co-route-name{
                        type string {
                            length 1..64;
                        }
                    }
                    leaf user-label{
                        type string {
                            length 0..242;
                        }
                    }
                    leaf bfd-enable {
                        type boolean;
                        default false;
                    }
                    container first-tunnel{
                        leaf tunnel-name {
                            type string {
                                length 1..64;
                            }
                        }
                    }
                    container second-tunnel{
                        leaf tunnel-name {
                            type string {
                                length 1..64;
                            }
                        }
                    }
                }
            }
        }
    }

   // Main container of oper

    container ute-tunnel-oper{
        config false;
        container p2p-tunnel{
            container tunnels{
                list tunnel{
                    key tunnel-name;
                    leaf tunnel-name{
                        type string {
                            length 1..64;
                        }
                        description "Tunnel Name";
                    }
                    leaf tunnel-type{
                        type identityref{
                            base tunl-type;
                        }
                        mandatory true;
                    }
                    leaf oper-status{
                        type ac-typeoperate-status;
                    }
                    leaf tunnel-id{
                        type uint32;
                    }
                    leaf sym-tunnel-name{
                        type string {
                            length 1..255;
                        }
                    }
                    container source{
                        uses src-or-dst;
                    }
                    container destination{
                        uses src-or-dst;
                    }
                }
            }
        }
    }

    // notification

    notification tunnel-state-down{
        leaf tunnel-name{
             type leafref{
                 path ute-tunnel-operp2p-tunneltunnelstunneltunnel-name;
             }
        }
    }

    notification tunnel-state-down-clear{
        leaf tunnel-name{
             type leafref{
                 path ute-tunnel-operp2p-tunneltunnelstunneltunnel-name;
             }
        }
        leaf reason {
            type  tunnel-down-clear-reason;
        }
    }
    notification tunnel-lsp-changed{
               leaf tunnel-name{
                   type leafref{
                     path ute-tunnel-operp2p-tunneltunnelstunneltunnel-name;
                   }
                }
                leaf oper-type{
                    type oper-type;
                }
                leaf sym-path-name{
                    type leafref{
                      path ute-tunnel-operp2p-tunneltunnelstunnelsym-tunnel-name;
                    }
                }
                container source{
                    uses src-or-dst;
                }
            }
} // <CODE ENDS>
