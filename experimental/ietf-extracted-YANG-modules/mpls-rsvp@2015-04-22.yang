module mpls-rsvp {

  yang-version "1";

  // namespace
  namespace "http://openconfig.net/yang/rsvp";

  prefix "rsvp";

  // import some basic types
  import ietf-inet-types { prefix inet; }
  import mpls-types { prefix mplst; }

  // meta
  organization "OpenConfig working group";

  contact
    "OpenConfig working group
    netopenconfig@googlegroups.com";

  description
    "Configuration for RSVP-TE signaling, including global protocol
    parameters and LSP-specific configuration for constrained-path
    LSPs";

  revision "2015-04-22" {
    description
      "Initial revision";
    reference "TBD";
  }

  // extension statements

  // feature statements

  // identity statements

  // typedef statements

  // grouping statements
  grouping mpls-rsvp-soft-preemption_config {
    description "Configuration for MPLS soft preemption";
    leaf enable {
      type boolean;
      default false;
      description "Enables soft preemption on a node.";
    }

    leaf soft-preemption-timeout {
      type uint16 {
        range 0..max;
      }
      // The RFC actually recommends 30 seconds as default.
      default 0;
      description "Timeout value for soft preemption to revert
        to hard preemption";
      reference "RFC5712 MPLS-TE soft preemption";
    }
  }

  grouping mpls-rsvp-soft-preemption {
    description "Top level group for MPLS soft preemption";
    container soft-preemption {
      description "Protocol options relating to RSVP
      soft preemption";
      container config {
        description "Configuration parameters relating to RSVP
        soft preemption support";
        uses mpls-rsvp-soft-preemption_config;
      }
      container state {
        description "State parameters relating to RSVP
        soft preemption support";
        config false;
        uses mpls-rsvp-soft-preemption_config;
      }
    }
  }

  grouping mpls-rsvp-protocol_options_config {
    description "RSVP protocol options configuration.";
    leaf hello-interval {
      type uint16 {
        range 1000..max;
      }
      default 9000;
      units milliseconds;
      description "set the interval in ms between RSVP hello
        messages";
    }
    leaf refresh-reduction {
      type boolean;
      default true;
      description "enables all RSVP refresh reduction message
        bundling, RSVP message ID, reliable message delivery
        and summary refresh";
      reference "RFC 2961 RSVP Refresh Overhead Reduction
        Extensions";
    }

    leaf refresh-reduction-reliable {
      type boolean;
      default true;
      description "enables RSVP refresh reduction reliable
        delivery and message_ID";
      reference "RFC 2961 RSVP Refresh Overhead Reduction
        Extensions";
    }
  }

  grouping mpls-rsvp-protocol_options {
    description "Top level group for RSVP protocol options";
    // TODO: confirm that the described semantics are supported
    // on various implementations. Finer grain configuration
    // will be vendor-specific
    container protocol_options {
      container config {
        description "Configuration for RSVP refresh reduction";
        uses mpls-rsvp-protocol_options_config;
      }
      container state {
        description "State for RSVP refresh reduction";
        config false;
        uses mpls-rsvp-protocol_options_config;
      }
    }
  }

  grouping mpls-rsvp-subscription_config {
    description "RSVP subscription configuration";
    leaf subscription {
      type mplst:percentage;
      description "percentage of the interface bandwidth that
        RSVP can reserve";
    }
  }
  grouping mpls-rsvp-subscription {
    description "Top level group for RSVP subscription options";
    container subscription {
      description "Bandwidth percentage reservable by RSVP
      on an interface";
      container config {
        uses mpls-rsvp-subscription_config;
      }
      container state {
        config false;
        uses mpls-rsvp-subscription_config;
      }
    }
  }

  grouping mpls-rsvp-graceful-restart_config {
    description
      "Configuration parameters relating to RSVP Graceful-Restart";

    leaf enable {
      type boolean;
      default false;
      description "Enables graceful restart on the node.";
    }

    leaf restart-time {
      type uint32;
      description
        "Graceful restart time (seconds).";
      reference
        "RFC 5495: Description of the Resource
        Reservation Protocol - Traffic-Engineered
        (RSVP-TE) Graceful Restart Procedures";
    }
    leaf recovery-time {
      type uint32;
      description
        "RSVP state recovery time";
    }
  }

  grouping mpls-rsvp-graceful-restart {
    description "Top level group for RSVP graceful-restart
    parameters";
    container graceful-restart {
      container config {
        description "Configuration parameters relating to
        graceful-restart";
        uses mpls-rsvp-graceful-restart_config;
      }
      container state {
        config false;
        description "State information associated with
        RSVP graceful-restart";
        uses mpls-rsvp-graceful-restart_config;
      }
    }
  }

  grouping mpls-rsvp-authentication_config {
    description "RSVP authentication parameters container.";
    leaf enable {
      type boolean;
      default false;
      description "Enables RSVP authentication on the node.";
    }
    leaf authentication-key {
      type string {
        // Juniper supports 1..16, Cisco has a much bigger range, up to 60.
        length "1..32";
      }
      description
        "authenticate RSVP signaling
        messages";
      reference
        "RFC 2747: RSVP Cryptographic Authentication";
    }
  }

  grouping mpls-rsvp-authentication {
    description "Top level group for RSVP authentication, as per RFC2747";
    container authentication {
      container config {
        description "Configuration parameters relating
        to authentication";
        uses mpls-rsvp-authentication_config;
      }
      container state {
        config false;
        description "State information associated
        with authentication";
        uses mpls-rsvp-authentication_config;
      }
    }
  }
  grouping mpls-rsvp-link-protection_config {
    description "RSVP facility (link/node) protection configuration";
    leaf enable {
      type boolean;
      default false;
      description "Enables facility protection on the interface.";
    }
    leaf link-protection-only {
      type boolean;
      default false;
      description "disables node protection on this interface,
                  and forces only link protection";
    }

    leaf bypass-optimize-interval {
      type uint16;
      units seconds;
      description "interval between periodic optimization
        of the bypass LSPs";
      // note: this is interface specific on juniper
      // on iox, this is global. need to resolve.
    }
    // to be completed, things like enabling link protection,
    // optimization times, etc.
  }

  grouping mpls-rsvp-link-protection {
    description "Top level group for RSVP protection";
    container link-protection {
      description "link-protection (NHOP) related configuration";
      container config {
        description "Configuration for link-protection";
        uses mpls-rsvp-link-protection_config;
      }
      container state {
        description "State for link-protection";
        config false;
        uses mpls-rsvp-link-protection_config;
      }

    }
  }

  grouping mpls-rsvp-error-statistics {
    description "RSVP-TE packet statistics";
    container error {
      description "RSVP-TE error statistics";
      leaf authentication-failure {
        type yang:counter32;
        description
          "Authentication failure count";
      }

      leaf PathErr {
        type yang:counter32;
        description
          "Path error to client count";
      }

      leaf ResvErr {
        type yang:counter32;
        description
          "Resv error to client count";
      }

      leaf path-timeout {
        type yang:counter32;
        description
          "Path timeout count";
      }

      leaf resv-timeout {
        type yang:counter32;
        description
          "Resv timeout count";
      }

      leaf rate-limit {
        type yang:counter32;
        description
          "Count of packets that were rate limited";
      }

      // TODO - complete the other error statistics
    }
  }

  grouping mpls-rsvp-protocol-statistics {
    description "RSVP protocol statistics";
    container protocol {
      description "RSVP-TE protocol statistics";
      leaf hello-sent {
        type yang:counter32;
        description
          "Hello sent count";
      }
      leaf hello-rcvd {
        type yang:counter32;
        description
          "Hello received count";
      }

      leaf path-sent {
        type yang:counter32;
        description
          "Path sent count";
      }

      leaf path-rcvd {
        type yang:counter32;
        description
          "Path received count";
      }

      // TODO - To be completed the other packet statistics
    }
  }

  grouping mpls-rsvp-statistics {
    description "RSVP-TE statistics";
    container statistics {
      description "Statistics related to RSVP-TE";
      container  config {
        description "Configuration for RSVP-TE statistics";
      }
      container state {
        config false;
        description "State for RSVP-TE statistics on an interface";
        uses mpls-rsvp-protocol-statistics;
        uses mpls-rsvp-error-statistics;
      }
    }
  }

  grouping rsvp-global {
    description "Global RSVP protocol configuration";
    container rsvp-te {
      description "RSVP-TE global signaling protocol configuration";

      container global {
        uses mpls-rsvp-graceful-restart;
        uses mpls-rsvp-soft-preemption;
        // TODO - reconcile global and per-interface protocol-related statistics
        uses mpls-rsvp-statistics;
      }
      // interfaces, bw percentages, hello timers, etc goes here";

      list interfaces {
        key interface-name;
        description "list of per-interface RSVP configurations";

        // TODO: update to interface ref -- move to separate
        // augmentation.
        leaf interface-name {
          type string;
          description "references a configured IP interface";
        }
        uses mpls-rsvp-protocol_options;
        uses mpls-rsvp-authentication;
        uses mpls-rsvp-subscription;
        // uses mpls-rsvp-ted-update-threshold; /* this moved to the te-global attributes stanza */
        uses mpls-rsvp-link-protection;

      }
    }
  }
}
