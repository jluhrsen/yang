submodule mpls-te {

  yang-version "1";

  belongs-to "mpls" {
    prefix "mpls";
  }

  // import some basic types
  import ietf-inet-types { prefix inet; }
  import mpls-types { prefix mplst; }
  import mpls-rsvp { prefix rsvp; }
  import mpls-sr { prefix sr; }

  // meta
  organization "OpenConfig working group";

  contact
    "OpenConfig working group
    netopenconfig@googlegroups.com";

  description
    "Configuration related to constrained-path LSPs and traffic
    engineering.  These definitions are not specific to a particular
    signaling protocol or mechanism (see related submodules for
        signaling protocol-specific configuration).";

  revision "2014-07-07" {
    description
      "Initial revision";
    reference "TBD";
  }

  // extension statements

  // feature statements

  // identity statements

  // using identities for path comp method, though enums may also
  // be appropriate if we decided these are the primary computation
  // mechanisms in future.
  identity path-computation-method {
    description "base identity for supported path computation
      mechanisms";
  }

  identity locally-computed {
    base path-computation-method;
    description "indicates a constrained-path LSP in which the
      path is computed by the local LER";
  }

  identity externally-queried {
    base path-computation-method;
    description "constrained-path LSP in which the path is
      obtained by querying an external source, such as a PCE server";
  }

  identity explicitly-defined {
    base path-computation-method;
    description "constrained-path LSP in which the path is
      explicitly specified as a collection of strict or/and loose
      hops";
  }

  // typedef statements

  typedef mpls-hop-type {
    type enumeration {
      enum LOOSE {
        description "loose hop in an explicit path";
      }
      enum STRICT {
        description "strict hop in an explicit path";
      }
    }
    description "enumerated type for specifying loose or strict
      paths";
  }

  typedef te-metric-type {
    type union {
      type enumeration {
        enum IGP {
          description "set the LSP metric to track the underlying
            IGP metric";
        }
      }
      type uint32;
    }
    description "union type for setting the LSP TE metric to a
      static value, or to track the IGP metric";
  }

  typedef cspf-tie-breaking {
    type enumeration {
      enum RANDOM {
        description "CSPF calculation selects a random path among
          multiple equal-cost paths to the destination";
      }
      enum LEAST_FILL {
        description "CSPF calculation selects the path with greatest
          available bandwidth";
      }
      enum MOST_FILL {
        description "CSPF calculation selects the path with the least
          available bandwidth";
      }
    }
    default RANDOM;
    description "type to indicate the CSPF selection policy when
      multiple equal cost paths are available";
  }

  typedef mpls-protection-style {
    type enumeration {
      enum UNPROTECTED {
        description "no protection is desired for the lsp";
      }
      enum LINK-PROTECTION-REQUESTED {
        description "link protection is desired for the lsp";
      }
      enum LINK-NODE-PROTECTION-REQUESTED {
        description "node and link protection is desired for the lsp";
      }
    }
    default UNPROTECTED;
    description
      "Specifies the protection type for the LSP";
  }

  // grouping statements

  grouping te_lsp_reoptimize_config {
    leaf te-lsp-reoptimize-timer {
      type uint16;
      units seconds;
      description "frequency of reoptimization of a te lsp";
    }
  }

  grouping te-lsp-common {
    description "common definitions for traffic-engineered LSPs";

    container config {
      uses te-lsp-common_config;
      uses te_lsp_reoptimize_config;
    }

    container state {
      config false;
      uses te-lsp-common_config;
      uses te_lsp_reoptimize_config;
    }

    container path-computation-method {
      description "select and configure the way the LSP path is
        computed";

      leaf path-computation {
        type identityref {
          base path-computation-method;
        }
        description "path computation method to use with the LSP";
      }

      uses te-lsp-comp-explicit;
      uses te-lsp-comp-queried;
      uses te-lsp-comp-local;
    }

    container path-attributes {
      description "general path attribute settings for TE-LSP
        tunnels";

      container config {
        description "configuration relating to LSP bandwidth
        and metrics";
        uses te-lsp-bandwidth_config;
        uses te-lsp-metric_config;
      }

      container state {
        description "operational state relating to LSP bandwidth
        and metrics";
        config false;
        uses te-lsp-bandwidth_config;
        uses te-lsp-metric_config;
      }

      // XXX - no, this is also there for LDP - also removed the
      // reference to "igp metric" as this is going to be confusing,
      // unless we mandate for the LSP to have the same metric as the
      // Igp, which is going to be hard with some vendors
      // implementations.

    }

    container lsp-placement-constraints {
      description
        "constraints on lsp routing such as admin-groups";

      container admin-groups {
        description
          "Include/Exclude constraints for link affinities";

        container exclude-groups {
          container config {
            description "configuration specifying admin
            groups which must be strictly excluded in the
            LSP path";
            uses te-lsp-exclude-admin-group_config;
          }
          container state {
            description "operational state reflecting
            admin groups which must be strictly excluded";
            config false;
            uses te-lsp-exclude-admin-group_config;
          }
        }
      }
      container include-any-groups {
        container config {
          description "configuration specifying admin
          groups, any of which must be included in the
          LSP path";
          uses te-lsp-include-any-admin-group_config;
        }
        container state {
          description "operational state relating to admin
          groups, any of which must be included in the
          LSP path";
          config false;
          uses te-lsp-include-any-admin-group_config;
        }
      }
      container include-all-groups {
          uses te-lsp-include-any-admin-group_config;
        container config {
          description "configuration specifying admin
          groups, all of which must be included in the
          LSP path";
          uses te-lsp-include-all-admin-group_config;
        }
        container state {
          description "operational state relating to admin
          groups, all of which must be included in the
          LSP path";
          config false;
          uses te-lsp-include-all-admin-group_config;
        }
      }
    }

    container protection {
      description "failure protection properties for the LSP";

      container config {
        description "configuration stating which MPLS protection
        options will be requested by the LSP";
        uses te-lsp-protection_config;
      }

      container state {
        description "operational state reflecting which
        MPLS protection options will be requested by the LSP";
        config false;
        uses te-lsp-protection_config;
      }

    }
  }

  grouping te-lsp-common_config {
    leaf signaled-name {
      type string;
      description "LSP name, also carried in signaling messages
        when appropriate";
    }

    leaf lsp-description {
      type string;
      description "optional text description for the LSP";
    }
    leaf destination {
      type inet:ip-address;
      description "destination egress node for the LSP";
    }
  }
}
