module cisco-openconfig-if-aggregate-devs {

  prefix  "lagdevs";

  namespace "http://cisco.com/ns/yang/cisco-openconfig-if-aggregate-devs";

  import openconfig-if-aggregate { prefix lag; }
  import openconfig-interfaces { prefix ocif; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-if-aggregate.yang@2015-11-20 

     on Cisco IOS-XR devices.

     Copyright (c) 2015-2016 by Cisco Systems, Inc.
     All rights reserved.";

  revision "2016-05-16" {
    description
      "Initial revision applicable to IOS-XR 6.0.1";
  }


  deviation /ocif:interfaces/ocif:interface/lag:aggregation/lag:config/lag:lag-type {
    deviate not-supported;
  }

  deviation /ocif:interfaces/ocif:interface/lag:aggregation/lag:state/lag:lag-type {
    deviate not-supported;
  }

  deviation /ocif:interfaces/ocif:interface/lag:aggregation/lag:state/lag:members {
    deviate not-supported;
  }

  deviation /ocif:interfaces/ocif:interface/lag:aggregation/lag:lacp/lag:config/lag:interval {
    deviate not-supported;
  }

  deviation /ocif:interfaces/ocif:interface/lag:aggregation/lag:lacp/lag:config/lag:lacp-mode {
    deviate not-supported;
  }

  deviation /ocif:interfaces/ocif:interface/lag:aggregation/lag:lacp/lag:state/lag:interval {
    deviate not-supported;
  }

  deviation /ocif:interfaces/ocif:interface/lag:aggregation/lag:lacp/lag:state/lag:lacp-mode {
    deviate not-supported;
  }

  deviation /ocif:interfaces/ocif:interface/lag:aggregation/lag:lacp/lag:members/lag:member/lag:state/lag:counters/lag:lacp-tx-errors {
    deviate not-supported;
  }
}
